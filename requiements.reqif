## 4.1-H: Common format across manufacturers (Interface Requirement)
The voting system manufacturer must support the NIST SP 1500 CDF specifications for export and interchange of data and reports across its major device categories.
- DeriveReqt -> 4.1

## 4.1-A: Data export and exchange format (Interface Requirement)
Voting devices must provide support for the non-restrictive, publicly-available NIST SP Common Data Format (CDF) specifications for data inputs and output:
• Election programming data, NIST SP 1500-100
• Election results data, NIST SP 1500-100
• Election event logging data, NIST SP 1500-101
• Voter registration-related data, NIST SP 1500-102
• Cast vote records, NIST SP 1500-103
• Ballot definition data, NIST SP 1500-104
- DeriveReqt -> 4.1

## 4.1-B: Election programming data input and output (Interface Requirement)
• input or output of election programming data;
• input or output of ballot programming data; and
• pre-election reports.
- DeriveReqt -> 4.1

## 4.1-D: Exchange of cast vote records (Interface Requirement)
Devices that export or import CVRs must support the NIST CDF specifications that apply to export and import of CVRs.
- DeriveReqt -> 4.1

## 4.1-E: Exchange of voting device election logs (Interface Requirement)
Voting devices must support the export or import of election log data using the NIST SP 1500-101 specification.
- DeriveReqt -> 4.1

## 4.1-G: Public specification of manufacturer native formats (Interface Requirement)
Where a NIST SP 1500 CDF specification or other interoperable interchange specification does not exist for a particular area of data interchange, the voting device manufacturer must provide a specification for its native format, describing how the manufacturer has implemented the native format that applies to the manufacturer’s specific voting devices and data. This includes such items as descriptions of elements, attributes, constraints, extensions, syntax and semantics of the format, and definitions for data fields and schemas.
- DeriveReqt -> 4.1
- Trace -> 4.1-F

## 4.1-F: Specification of common format usage (Interface Requirement)
The voting device or election system manufacturer must provide a specification describing how the manufacturer has implemented a NIST SP 1500 CDF specification that applies to the manufacturer’s specific voting devices and data. This includes such items as descriptions of elements, attributes, constraints, extensions, syntax and semantics of the format, and definitions for data fields and schemas.
- DeriveReqt -> 4.1

## 4.1-C: Tabulator report data (Interface Requirement)
Tabulators must include support for the NIST CDF specifications for election results reporting data.
- DeriveReqt -> 4.1
- Trace -> 4.1-D

## R9: User-centered design process (Functional Requirement)
The manufacturer must submit a report providing documentation that the system was developed following best practices for a user-centered design process.
The report must include, at a minimum:
•A listing of user-centered design methods used
•The types of voters and election workers included in those methods
•How those methods were integrated into the overall implementation process
•How the results of those methods contributed to developing the final features and design of the voting system
- DeriveReqt -> 2.2

## 1: High Quality Design (Requirement)
The voting system is designed to accurately, completely, and robustly carry out election processes.

## 1.3: Identify correct implementations (Business Requirement)
Voting system design supports evaluation methods enabling testers to clearly distinguish systems that correctly implement specified properties from those that do
not.

## 1.1: Process Specifications (Business Requirement)
The voting system is designed using commonly-accepted election process specifications.

## 1.2: Real World (Business Requirement)
The voting system is designed to function correctly under real-world operating conditions.

## 2: High Quality Implementation (Requirement)
The voting system is implemented using high quality best practices.

## 2.1: Best Practices (Requirement)
The voting system and its software are implemented using trustworthy materials and best practices in software development.

## 2.2: User Centered (Requirement)
The voting system is implemented using best practice user-centered design methods, for a wide range of representative voters, including those with and without disabilities, and election workers.

## 4: Interoperable (Requirement)
The voting system is designed to support interoperability in its interfaces to external systems, its interfaces to internal components, its data, and its peripherals.

## 4.1: Interoperable Formats (Requirement)
Voting system data that is imported, exported, or otherwise reported, is in an interoperable format.

## 4.2: Standard Formats (Requirement)
Standard, publicly-available formats for other types of data are used, where available.

## 4.3: Widely-used protocols (Requirement)
Widely-used hardware interfaces and communications protocols are used.

## 17: Election definition devices, ballot definition (Requirement)
The election definition device MUST provide for the logical definition of the ballot, including the definition of the number of allowable votes for each contest.
- Trace -> R26

## R22: Election definition devices, administrative subdivisions (Functional Requirement)
The election definition device MUST provide for the logical definition of administrative subdivisions, where the list contests varies between subdivisions.

## R23: Election definition devices, ballot definition details (Requirement)
The election definition device MUST be capable of collecting and maintaining
Contests and their associated labels and instructions;
Candidate names and their associated labels; and
Ballot questions and their associated text.
- Trace -> R26

## R24: Election definition devices, election districts (Functional Requirement)
The election definition device MUST enable EOs to define multiple election districts.

## R25: Election definition devices, identifiers (Functional Requirement)
The election definition device MUST enable EOs to associate a minimum of 3 identifiers each for administration subdivisions, election districts, contests, and candidates.

## R26: Election definition devices (Class)

## R27: Voting System (Class)

## 20: Integratability of systems and devices (Interface Requirement)
Systems MUST maximize integratability with other systems and/or devices of other systems.

## 21: Standard device interfaces (Interface Requirement)
Standard, common hardware interfaces and protocols MUST be used to connect devices.
- Refine -> 20

## 22: Standard protocols and algorithms (Interface Requirement)
Standard, publicly-available and publicly-documented protocols MUST be used, where possible, for exchanging data or encoding data.
- Refine -> 20
